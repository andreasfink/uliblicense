UMLicenseRestriction ::= CHOICE {
    lockedToMacAddresses    [1] UTF8String,
    lockedToUUID            [2] UTF8String,
    lockedToIps             [3] UTF8String,
    lockedToSerials         [4] UTF8String,
    lockedToOperatingSystem [5] UTF8String,
    lockedToLegacySerial [6] UTF8String,
}
