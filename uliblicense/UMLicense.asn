UMLicense ::= SEQUENCE {
    licenseSerialNumber     [0] UTF8String,
    licenseType             [1] UTF8String,
    licenseOwner            [2] UTF8String,
    licenseRestrictions     [3] UMLicenseRestrictionList OPTIONAL,
    licenseProducts         [4] UMLicenseProductList,
    licenseExpiration       [5] UTF8String,
    licenseRenewUrl         [6] UTF8String OPTIONAL,
    licenseRenewAddress     [7] UTF8String OPTIONAL,
    licenseRenewTimerMin    [8] INTEGER OPTIONAL,
    licenseRenewTimerMax    [9] INTEGER OPTIONAL,
    licenseEmail            [10] UTF8String,
    licenseReportUrl        [11] UTF8String OPTIONAL,
    licenseReportAddress    [12] UTF8String OPTIONAL,
    licenseReportTimer      [13] INTEGER OPTIONAL,
    ...
}
